(setvar "CMDECHO" 0)
(setq types '())
(setq ss (ssget "_X"))
(if ss
  (progn
    (setq i 0 n (sslength ss))
    (while (< i n)
      (setq e (entget (ssname ss i)))
      (setq ty (cdr (assoc 0 e)))
      (setq pair (assoc ty types))
      (if pair
        (setq types (subst (cons ty (1+ (cdr pair))) pair types))
        (setq types (cons (cons ty 1) types))
      )
      (setq i (1+ i))
    )
  )
)
(princ "\nENTITIES:")
(foreach p types (princ (strcat "\n " (car p) "=" (itoa (cdr p)))))
(setq ss (ssget "_X" '((0 . "CIRCLE"))) i 0)
(if ss
  (progn
    (princ (strcat "\nCIRCLES=" (itoa (sslength ss))))
    (repeat (sslength ss)
      (setq e (entget (ssname ss i)))
      (setq c (cdr (assoc 10 e)))
      (setq r (cdr (assoc 40 e)))
      (setq el (cdr (assoc 38 e)))
      (if (not el) (setq el (if (caddr c) (caddr c) 0.0)))
      (princ (strcat "\n C=" (rtos (car c) 2 4) "," (rtos (cadr c) 2 4) " r=" (rtos r 2 4) " z=" (rtos el 2 4)))
      (setq i (1+ i))
    )
  )
  (princ "\nCIRCLES=0")
)
(command "_.ZOOM" "_E")
(setq a (getvar "EXTMIN") b (getvar "EXTMAX"))
(princ (strcat "\nEXT=" (rtos (car a) 2 3) ".." (rtos (car b) 2 3) " Z=" (rtos (caddr a) 2 3) ".." (rtos (caddr b) 2 3)))
(princ "\nOK-HOLES")
(princ)
