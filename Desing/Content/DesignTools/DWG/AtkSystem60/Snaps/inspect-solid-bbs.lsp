(setvar "CMDECHO" 0)
(setvar "OSMODE" 0)
(setq ss (ssget "_X" '((0 . "3DSOLID"))))
(if ss
  (progn
    (setq i 0 n (sslength ss))
    (while (< i n)
      (setq en (ssname ss i))
      (command "_.ZOOM" "_OB" en "")
      (setq a (getvar "EXTMIN") b (getvar "EXTMAX"))
      (princ (strcat "\nS" (itoa i)
        " " (rtos (car a) 2 3) "," (rtos (cadr a) 2 3) "," (rtos (caddr a) 2 3)
        " .. " (rtos (car b) 2 3) "," (rtos (cadr b) 2 3) "," (rtos (caddr b) 2 3)
        " dX=" (rtos (- (car b) (car a)) 2 3)
        " dZ=" (rtos (- (caddr b) (caddr a)) 2 3)))
      (setq i (1+ i))
    )
  )
)
(princ "\nOK-BBOX")
(princ)
