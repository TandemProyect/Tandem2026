; Panel universal 27104219: solo recorte de altura. El ancho 0,75 y las U no se tocan.
(defun keep-in-box (p1 p2 / ss i n en box pair)
  (setq ss (ssget "_X" '((0 . "3DSOLID"))))
  (if ss
    (progn
      (setq i 0 n (sslength ss))
      (while (< i n)
        (setq en (ssname ss i))
        (if (entget en)
          (progn
            (command "_.BOX" p1 p2)
            (setq box (entlast) pair (ssadd))
            (ssadd en pair)
            (ssadd box pair)
            (command "_.INTERSECT" pair "")
            (if (and box (entget box))
              (progn (if (entget en) (entdel en)) (entdel box))
            )
          )
        )
        (setq i (1+ i))
      )
    )
  )
)
(defun del-circ-beyond-z (z / ss i en p)
  (setq ss (ssget "_X" '((0 . "CIRCLE"))))
  (if ss
    (progn
      (setq i (1- (sslength ss)))
      (while (>= i 0)
        (setq en (ssname ss i) p (cdr (assoc 10 (entget en))))
        (if (> (cadr p) (+ z 0.0001)) (entdel en))
        (setq i (1- i))
      )
    )
  )
)
(defun mirror-xy (z / ss)
  (setq ss (ssget "_X" '((0 . "3DSOLID,CIRCLE"))))
  (if ss (command "_.MIRROR3D" ss "" "_XY" (list 0.0 0.0 z) "_N"))
)
(defun union-pair (a b / pair)
  (if (and a b (entget a) (entget b) (not (eq a b)))
    (progn
      (setq pair (ssadd))
      (ssadd a pair)
      (ssadd b pair)
      (command "_.UNION" pair "")
    )
  )
)
(defun news-not-in (ss0 / all k a out)
  (setq all (ssget "_X" '((0 . "3DSOLID"))) out '())
  (if all
    (progn
      (setq k 0)
      (while (< k (sslength all))
        (setq a (ssname all k))
        (if (not (ssmemb a ss0)) (setq out (append out (list a))))
        (setq k (1+ k))
      )
    )
  )
  out
)
(defun union-mirrors (ss0 / n i news)
  (if ss0
    (progn
      (setq n (sslength ss0) news (news-not-in ss0) i 0)
      (while (and (< i n) (< i (length news)))
        (union-pair (ssname ss0 i) (nth i news))
        (setq i (1+ i))
      )
    )
  )
)
(defun union-solids ( / ss n)
  (setvar "SOLIDHIST" 0)
  (setq ss (ssget "_X" '((0 . "3DSOLID"))))
  (if (and ss (> (sslength ss) 1)) (command "_.UNION" ss ""))
  (setq ss (ssget "_X" '((0 . "3DSOLID"))) n (if ss (sslength ss) 0))
  (princ (strcat "\nSOLIDS=" (itoa n)))
)
(defun cut-height ( / half ss0 src)
  (setq src (if *SRC_H* *SRC_H* 2.40))
  (if (> (abs (- *H* src)) 0.001)
    (progn
      (setq half (/ *H* 2.0))
      (keep-in-box (list -1.0 -1.0 -0.02) (list 2.0 1.0 (+ half *OLAP*)))
      (del-circ-beyond-z half)
      (setq ss0 (ssget "_X" '((0 . "3DSOLID"))))
      (mirror-xy half)
      (union-mirrors ss0)
      (union-solids)
    )
    (princ "\nSOLIDS=keep")
  )
)
(defun c:MAKE3D ( / )
  (if (not *OLAP*) (setq *OLAP* 0.010))
  (if (not *SRC_H*) (setq *SRC_H* 2.40))
  (setvar "OSMODE" 0)
  (setvar "CMDECHO" 0)
  (setvar "DELOBJ" 1)
  (setvar "SOLIDHIST" 0)
  (cut-height)
  (setvar "INSBASE" (list 0.0 0.0 0.0))
  (princ (strcat "\nOK-" *LBL*))
  (princ)
)
(c:MAKE3D)
(command "_.QSAVE")
(princ)
