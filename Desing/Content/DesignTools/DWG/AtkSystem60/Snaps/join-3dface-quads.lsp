; Empareja 3DFACE triangulares coplanares que comparten arista -> quad (4 vertices).
; Quita las diagonales del STL. INSBASE no se toca.
(defun dxf (c v) (cons c v))
(defun pt= (a b) (equal a b 0.0005))
(defun pkey (p)
  (strcat (rtos (car p) 2 4) "," (rtos (cadr p) 2 4) "," (rtos (caddr p) 2 4))
)
(defun ekey (a b / ka kb)
  (setq ka (pkey a) kb (pkey b))
  (if (< ka kb) (strcat ka "|" kb) (strcat kb "|" ka))
)
(defun vsub (a b) (mapcar '- a b))
(defun vdot (a b) (apply '+ (mapcar '* a b)))
(defun vcrs (u v)
  (list
    (- (* (cadr u) (caddr v)) (* (caddr u) (cadr v)))
    (- (* (caddr u) (car v)) (* (car u) (caddr v)))
    (- (* (car u) (cadr v)) (* (cadr u) (car v)))
  )
)
(defun vunit (n / len)
  (setq len (sqrt (vdot n n)))
  (if (< len 1.0e-12) nil (mapcar '(lambda (x) (/ x len)) n))
)
(defun face-pts (e / p0 p1 p2 p3)
  (setq p0 (cdr (assoc 10 e)) p1 (cdr (assoc 11 e))
        p2 (cdr (assoc 12 e)) p3 (cdr (assoc 13 e)))
  (if (or (not p3) (pt= p2 p3) (pt= p0 p3))
    (list p0 p1 p2)
    (list p0 p1 p2 p3)
  )
)
(defun face-n (pts / n)
  (setq n (vcrs (vsub (cadr pts) (car pts)) (vsub (caddr pts) (car pts))))
  (vunit n)
)
(defun pt-in (p lst / found q)
  (setq found nil)
  (foreach q lst (if (pt= p q) (setq found T)))
  found
)
(defun same-plane (pts1 pts2 n1 / ok p)
  (setq ok T)
  (foreach p pts2
    (if (> (abs (vdot n1 (vsub p (car pts1)))) 0.0005) (setq ok nil))
  )
  (and ok n1 (setq n2 (face-n pts2)) n2 (> (vdot n1 n2) 0.999))
)
(defun mk-quad (t1 t2 / a b c d iu)
  (setq iu 0)
  (if (pt-in (car t1) t2) (setq iu 1))
  (if (and (= iu 1) (pt-in (cadr t1) t2)) (setq iu 2))
  (setq a (nth iu t1)
        b (nth (rem (1+ iu) 3) t1)
        c (nth (rem (+ iu 2) 3) t1))
  (setq d nil)
  (foreach p t2 (if (not (pt-in p t1)) (setq d p)))
  (if d (list a b d c) nil)
)
(defun convex-q (q n / i e1 e2 ok)
  (setq ok T i 0)
  (while (and ok (< i 4))
    (setq e1 (vsub (nth (rem (1+ i) 4) q) (nth i q)))
    (setq e2 (vsub (nth (rem (+ i 2) 4) q) (nth (rem (1+ i) 4) q)))
    (if (< (vdot (vcrs e1 e2) n) -1.0e-9) (setq ok nil))
    (setq i (1+ i))
  )
  ok
)
(defun add-edge (emap key idx / pair)
  (setq pair (assoc key emap))
  (if pair
    (subst (cons key (append (cdr pair) (list idx))) pair emap)
    (cons (cons key (list idx)) emap)
  )
)
(defun c:JOINQUADS ( / ss i n e pts recs rec emap key used pairs
                       idx idxs ia ib ra rb q nn lay col hx en1 en2
                       nquad nleft)
  (setq ss (ssget "_X" '((0 . "3DFACE"))))
  (if (not ss)
    (princ "\nJOINQUADS none")
    (progn
  (setq i 0 n (sslength ss) recs nil)
  (while (< i n)
    (setq e (entget (ssname ss i)))
    (setq pts (face-pts e))
    (setq recs (append recs (list (list (ssname ss i) pts e))))
    (setq i (1+ i))
  )
  (setq emap nil i 0)
  (foreach rec recs
    (setq pts (cadr rec))
    (if (= (length pts) 3)
      (progn
        (setq emap (add-edge emap (ekey (nth 0 pts) (nth 1 pts)) i))
        (setq emap (add-edge emap (ekey (nth 1 pts) (nth 2 pts)) i))
        (setq emap (add-edge emap (ekey (nth 2 pts) (nth 0 pts)) i))
      )
    )
    (setq i (1+ i))
  )
  (setq used (mapcar '(lambda (x) nil) recs) pairs nil)
  (foreach pair emap
    (setq idxs (cdr pair))
    (if (= (length idxs) 2)
      (progn
        (setq ia (car idxs) ib (cadr idxs))
        (if (and (not (nth ia used)) (not (nth ib used)))
          (progn
            (setq ra (nth ia recs) rb (nth ib recs))
            (setq nn (face-n (cadr ra)))
            (if (and nn (same-plane (cadr ra) (cadr rb) nn))
              (progn
                (setq q (mk-quad (cadr ra) (cadr rb)))
                (if (and q (convex-q q nn))
                  (progn
                    (setq used (add-used used ia T))
                    (setq used (add-used used ib T))
                    (setq pairs (cons (list ia ib q) pairs))
                  )
                )
              )
            )
          )
        )
      )
    )
  )
  (setq nquad 0)
  (foreach pr pairs
    (setq ra (nth (car pr) recs) rb (nth (cadr pr) recs) q (caddr pr))
    (setq e (caddr ra))
    (setq lay (cdr (assoc 8 e)) col (cdr (assoc 62 e)) hx (cdr (assoc 420 e)))
    (entdel (car ra))
    (entdel (car rb))
    (setq e (list (dxf 0 "3DFACE") (dxf 100 "AcDbEntity") (dxf 8 (if lay lay "0"))))
    (if col (setq e (append e (list (dxf 62 col)))))
    (if hx (setq e (append e (list (dxf 420 hx)))))
    (setq e (append e (list
      (dxf 100 "AcDbFace")
      (dxf 10 (nth 0 q)) (dxf 11 (nth 1 q)) (dxf 12 (nth 2 q)) (dxf 13 (nth 3 q))
    )))
    (entmake e)
    (setq nquad (1+ nquad))
  )
  (setq nleft 0 i 0)
  (foreach u used
    (if (not u) (setq nleft (1+ nleft)))
    (setq i (1+ i))
  )
  (princ (strcat "\nOK-JOINQUADS quads=" (itoa nquad) " leftover=" (itoa nleft)))
  (princ)
    )
  )
)
(defun add-used (lst idx val / i n out)
  (setq i 0 n (length lst) out nil)
  (repeat n
    (setq out (append out (list (if (= i idx) val (nth i lst)))))
    (setq i (1+ i))
  )
  out
)
(c:JOINQUADS)
(if *JOINOUT*
  (command "_.SAVEAS" "2018" *JOINOUT*)
)
(princ)
