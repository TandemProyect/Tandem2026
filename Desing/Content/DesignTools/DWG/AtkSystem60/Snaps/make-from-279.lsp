; Estrecha/baja 27904209R a *W* x *H*. INSBASE = 0,0,0 (inferior izquierda).
; Ancho: si W>=0,45, mismo criterio que 276 (X>0,45 se mueve). Si W=0,30, se conserva el perfil.
; Alto 2,40: Z>1,35 se mueve -0,30 (grapas 550). Alto 1,20: grapas 350 (manual).
(defun dxf (c v) (cons c v))
(defun map-x (x)
  (cond
    ((< (abs (- *W* 0.90)) 0.001) x)
    ((>= *W* 0.449)
      (if (> x 0.45) (+ x (- *W* 0.90)) x)
    )
    ((<= x 0.05) x)
    ((>= x 0.85) (- *W* (- 0.90 x)))
    (T (+ 0.05 (* (- x 0.05) (/ (- *W* 0.10) 0.80))))
  )
)
(defun map-z (z)
  (cond
    ((< (abs (- *H* 2.70)) 0.001) z)
    ((< (abs (- *H* 2.40)) 0.001)
      (if (> z 1.35) (+ z -0.30) z)
    )
    ((<= z 0.55) (* z (/ 0.35 0.55)))
    ((>= z 2.15) (+ 0.85 (* (- z 2.15) (/ 0.35 0.55))))
    (T (+ 0.35 (* (- z 0.55) (/ 0.50 1.60))))
  )
)
(defun is-ocs (e / n)
  (setq n (cdr (assoc 210 e)))
  (and n (listp n) (numberp (cadr n)) (equal (cadr n) -1.0 0.05))
)
(defun map-pt (p ocs / x y z)
  (setq x (car p) y (cadr p))
  (setq z (if (and p (cddr p) (numberp (caddr p))) (caddr p) nil))
  (if ocs
    (if z (list (map-x x) (map-z y) z) (list (map-x x) (map-z y)))
    (if z (list (map-x x) y (map-z z)) (list (map-x x) y))
  )
)
(defun stretch-ename (en / e n g p ocs)
  (setq e (entget en) n nil ocs (is-ocs e))
  (foreach g e
    (cond
      ((member (car g) '(10 11 12 13))
        (setq n (append n (list (cons (car g) (map-pt (cdr g) ocs)))))
      )
      ((= (car g) 1)
        (setq p (cdr g))
        (if (equal p "2,70x90") (setq p *LBL*))
        (setq n (append n (list (cons 1 p))))
      )
      (T (setq n (append n (list g))))
    )
  )
  (if n (entmod n))
)
(defun c:NARROW ( / ss i n en)
  (setq ss (ssget "_X"))
  (if ss
    (progn
      (setq i 0 n (sslength ss))
      (while (< i n)
        (setq en (ssname ss i))
        (stretch-ename en)
        (setq i (1+ i))
      )
    )
  )
  (setvar "INSBASE" (list 0.0 0.0 0.0))
  (princ (strcat "\nOK-" *LBL*))
  (princ)
)
(c:NARROW)
(command "_.QSAVE")
(princ)
